Attribute VB_Name = "Counter_Sinking"
'Language = "VBSCRIPT"

'*******************************************************************************************
'*
'* Procedure that allow the user to insert an axial  sequential operation
'*
'*    Open CATProcess and load Machining workbench
'*    Execute the VB Script Macro
'*
'*******************************************************************************************

'*********************************
'Global variables
'********************************

Dim MfgDoc1 As Document
Dim ActivityRef As AnyObject
Dim Setup1 As ManufacturingSetup
Dim Program1 As ManufacturingProgram
Dim ncProd As Product                         ' Product including the Design Part
Dim documents1 As Documents
Dim partDocument1 As Document

'*******************************************************************************************
'*              Main Entry  Point
'*******************************************************************************************

Sub CATMain()

        

    Dim ProgramList As MfgActivities
    Dim NumberOfPO As Integer
    Dim childs As Activities
    Dim child As Activity
    Dim quantity As Integer
'    Dim Line1 As CATIABase
'    Dim Point1 As CATIABase
'    Dim Point2 As CATIABase
'    Dim Point3 As CATIABase
'    Dim Plane2 As CATIABase
'    Dim Line2 As CATIABase
'    Dim Line3 As CATIABase
    
    '*******************************************************************************************
    '*** Retrieve the Open body of the part
    '*******************************************************************************************

    Set documents1 = CATIA.Documents
    Set partDocument1 = documents1.Item("test_geo.CATPart")

    Set part1 = partDocument1.Part
    Set hybridBodies1 = part1.HybridBodies
    Set hybridBody1 = hybridBodies1.Item("geo2")
    Set hybridShapes1 = hybridBody1.HybridShapes

    '*******************************************************************************************
    '*** Retrieve the tool motion's geometry
    '*******************************************************************************************

    'Set Plane1 = hybridShapes1.Item("Plane.1")
    'Set Line1 = hybridShapes1.Item("Line.1")
    Set Point5 = hybridShapes1.Item("Point.5")
    Set Point6 = hybridShapes1.Item("Point.6")
    Set Point7 = hybridShapes1.Item("Point.7")
    'Set Plane2 = hybridShapes1.Item("Plane.2")
    'Set Line2 = hybridShapes1.Item("Line.2")
    'Set Line3 = hybridShapes1.Item("Line.3")

    Set MfgDoc1 = CATIA.ActiveDocument
    Debug.Print MfgDoc1.Name
    '*******************************************************************************************
    '*** Retrieve current Process Root
    '*******************************************************************************************

    Set ActivityRef = MfgDoc1.GetItem("Process")
    Debug.Print ActivityRef.Name
    
    '*** Retrieve current SetUp
    '***
    If (ActivityRef.IsSubTypeOf("PhysicalActivity")) Then

    Set childs = ActivityRef.ChildrenActivities
    quantity = childs.Count

    If quantity <= 0 Then
      Exit Sub
    End If
    NumberOfPO = 0
    For i = 1 To quantity
        Set child = childs.Item(i)
        Debug.Print child.Name
        If (child.IsSubTypeOf("ManufacturingSetup")) Then
            Set Setup1 = child
            NumberOfPO = NumberOfPO + 1
            Exit For
        End If
    Next
    
    End If
    
    
    '---------------------------------------------------------------
    ' Retrieve the Manufacturing View
    '---------------------------------------------------------------
    Dim MfgView As ManufacturingView
    Set MfgView = Setup1.GetManufacturingView
    
    Debug.Print MfgView.Name

    
    '*******************************************************************************************
    '*** Retrieve current Program
    '*******************************************************************************************

    Set ProgramList = Setup1.Programs
    Debug.Print ProgramList.Name
    
    Set ncProd = Setup1.Product
    Debug.Print ncProd.Name
    
    Set Program1 = ProgramList.GetElement(1)
    Debug.Print Program1.Name
    Debug.Print Program1.Type
    

    '*******************************************************************************************
    ' Creation axial sequential operation
    '*******************************************************************************************

    Dim Mo As ManufacturingOperation
    Set Mo = Program1.GetItem("Counter Sinking.4")

    Debug.Print Mo.Name
    


    '---------------------------------------------------------------
    ' Create a Machining Pattern
    '---------------------------------------------------------------
    Dim Features As ManufacturingFeatures
    Set Features = MfgView.ManufacturingFeatures
    
    Dim myMfgPattern As ManufacturingPattern
    Set myMfgPattern = Features.Add("MfgPatternUsage")
    Debug.Print myMfgPattern.Name
    
    
    'Dim OrderingMode As Variant
    'Set OrderingMode = myMfgPattern.GetAnAttribute("TopMode ")
    'Debug.Print OrderingMode.Value





    'add the point as last pattern point
    
    For i = 1 To hybridShapes1.Count
        Set Pt = hybridShapes1.Item(i)
        Call myMfgPattern.AddPosition(Pt, ncProd, 0)
        Call myMfgPattern.SetLocalToolAxis(i, 1, 0, 1 + i * 0.000001)
    Next i
    

End Sub

Attribute VB_Name = "Module1_PtoP"
'Language = "VBSCRIPT"

'*******************************************************************************************
'*
'* Procedure that allow the user to insert an axial  sequential operation
'*
'*    Open CATProcess and load Machining workbench
'*    Execute the VB Script Macro
'*
'*******************************************************************************************

'*********************************
'Global variables
'********************************

Dim MfgDoc1 As Document
Dim ActivityRef As AnyObject
Dim Setup1 As ManufacturingSetup
Dim Program1 As ManufacturingProgram
Dim PartMachined As Product                         ' Product including the Design Part
Dim documents1 As Documents
Dim partDocument1 As Document

'*******************************************************************************************
'*              Main Entry  Point
'*******************************************************************************************

Sub CATMain()

        

    Dim ProgramList As MfgActivities
    Dim NumberOfPO As Integer
    Dim childs As Activities
    Dim child As Activity
    Dim quantity As Integer
'    Dim Line1 As CATIABase
'    Dim Point1 As CATIABase
'    Dim Point2 As CATIABase
'    Dim Point3 As CATIABase
'    Dim Plane2 As CATIABase
'    Dim Line2 As CATIABase
'    Dim Line3 As CATIABase
    
    '*******************************************************************************************
    '*** Retrieve the Open body of the part
    '*******************************************************************************************

    Set documents1 = CATIA.Documents
    Set partDocument1 = documents1.Item("test_geo.CATPart")

    Set part1 = partDocument1.Part
    Set hybridBodies1 = part1.HybridBodies
    Set hybridBody1 = hybridBodies1.Item("geo")
    Set hybridShapes1 = hybridBody1.HybridShapes

    '*******************************************************************************************
    '*** Retrieve the tool motion's geometry
    '*******************************************************************************************

    Set Plane1 = hybridShapes1.Item("Plane.1")
    Set Line1 = hybridShapes1.Item("Line.1")
    Set Point1 = hybridShapes1.Item("Point.1")
    Set Point2 = hybridShapes1.Item("Point.2")
    Set Point3 = hybridShapes1.Item("Point.3")
    Set Plane2 = hybridShapes1.Item("Plane.2")
    Set Line2 = hybridShapes1.Item("Line.2")
    Set Line3 = hybridShapes1.Item("Line.3")

    Set MfgDoc1 = CATIA.ActiveDocument
    Debug.Print MfgDoc1.Name
    '*******************************************************************************************
    '*** Retrieve current Process Root
    '*******************************************************************************************

    Set ActivityRef = MfgDoc1.GetItem("Process")
    Debug.Print ActivityRef.Name
    
    '*** Retrieve current SetUp
    '***
    If (ActivityRef.IsSubTypeOf("PhysicalActivity")) Then

    Set childs = ActivityRef.ChildrenActivities
    quantity = childs.Count

    If quantity <= 0 Then
      Exit Sub
    End If
    NumberOfPO = 0
    For i = 1 To quantity
        Set child = childs.Item(i)
        Debug.Print child.Name
        If (child.IsSubTypeOf("ManufacturingSetup")) Then
            Set Setup1 = child
            NumberOfPO = NumberOfPO + 1
            Exit For
        End If
    Next
     
    End If
    
    
    
    
    
    
    
    
    '*******************************************************************************************
    '*** Retrieve current Program
    '*******************************************************************************************

    Set ProgramList = Setup1.Programs
    Debug.Print ProgramList.Name
    
    Set PartMachined = Setup1.Product
    Debug.Print PartMachined.Name
    
    Set Program1 = ProgramList.GetElement(1)
    Debug.Print Program1.Name
    Debug.Print Program1.Type
    

    '*******************************************************************************************
    ' Creation axial sequential operation
    '*******************************************************************************************

    Dim Mo As ManufacturingOperation
    
    For i = 1 To Program1.Activities.Count
        Set Mo = Program1.Activities.GetElement(i)
        If Mo.Name = "Point to Point .1" Then Exit For
    Next i
    
    Debug.Print Mo.Name
    

    '*******************************************************************************************
    ' Creation of point tool motion
    '*******************************************************************************************

    Dim Tm1 As ManufacturingToolMotion
    
    For i = 1 To 1000
    Set Tm1 = Mo.InsertToolMotion("MfgSeqMotionPoint", 1)
    Debug.Print Tm1.Name
    
    'Call Tm1.SetGotoPtPointCoordinates(25.4, 11.1, -25.4) not worked
    Call Tm1.SetGeometry("PointSite", Point1, PartMachined, 0)
    
    Call Mo.SetToolAxis(1, 2, 3)
    Next i

    
    Set Tm1 = Mo.InsertToolMotion("MfgSeqMotionPoint", 1)
    Debug.Print Tm1.Name
    
    'Call Tm1.SetGeometry("AxisOrientation", Point2, PartMachined, 0)
    
    'Set AxisMode = Tm1.GetAttribute("TMToolAxis_VectorX")
    Set AxisMode = Tm1.GetAttribute("MfgGlobalAxisMode")
    
    
    
    Call Mo.SetToolAxis(3, 2, 1)
    
    
    

    '*******************************************************************************************
    ' Creation of position tool motion
    '*******************************************************************************************

    'Dim Tm2 As ToolMotion
    Set Tm2 = Mo.InsertToolMotion("MfgSeqMotionPosition", 2)

    Call Tm2.SetGeometry("Parts", Plane1, PartMachined, 0)
    Call Tm2.SetGeometry("FirstRelimitingElement", Line2, PartMachined, 0)
    Call Tm2.SetGeometry("Drives", Line3, PartMachined, 0)
    Call Tm2.SetGeometry("RelimitingElements", Point3, PartMachined, 0)

    '*******************************************************************************************
    ' Modification of Position on check parameter
    '*******************************************************************************************
    Dim CheckMode As Variant
    Set CheckMode = Tm2.GetAttribute("MfgCheckStopMode")
    CheckMode.ValuateFromString ("MfgTo")

    '*******************************************************************************************
    ' Creation of delta tool motion
    '*******************************************************************************************
    'Dim Tm3 As ToolMotion
    Set Tm3 = Mo.InsertToolMotion("MfgSeqMotionDelta", 3)
    Set CheckMode = Tm3.GetAttribute("MfgPtDeltaMode")
    CheckMode.ValuateFromString ("MfgPtDeltaParallelLine")
    Call Tm3.SetGeometry("GuidingElements", Line2, PartMachined, 0)
    Dim OffsetValue As Variant
    Set OffsetValue = Tm3.GetAttribute("MfgPtDeltaDistance")
    OffsetValue.Value = 15

    '*******************************************************************************************
    ' get the list of tool motions and reading each tool motion
    '*******************************************************************************************
    Dim TMList2 As MfgToolMotions
    Set TMList2 = Mo.GetListOfToolMotions
    NbMo = TMList2.Count
    Dim Test2 As ManufacturingToolMotion
    Set Test2 = TMList2.GetElement(1)
    'msgbox(Test2.Name)
    Set Test2 = TMList2.GetElement(2)
    'msgbox(Test2.Name)
    Set Test2 = TMList2.GetElement(3)
    'msgbox(Test2.Name)

End Sub
